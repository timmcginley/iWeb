;;;ontzetter
(defun c:ontzet ()
 
  (setq elm (entget (car (entsel "\NSelecteer een element"))))
  (setq teller 0)
  (repeat (length elm)
     (if (or (assoc 10 (list(nth teller elm)) ) 
             (assoc 11 (list(nth teller elm)) )
             (assoc 12 (list(nth teller elm)) )
             (assoc 13 (list(nth teller elm)) )
             (assoc 20 (list(nth teller elm)) )
             (assoc 21 (list(nth teller elm)) )
             (assoc 30 (list(nth teller elm)) )
             (assoc 31 (list(nth teller elm)) ) 
         )
       (if (= (length (nth teller elm)) 4)
         (progn
           (print (nth teller elm))
           (setq deel1 (nth teller elm)) 
           (setq deel2 (list (nth 0 deel1) (nth 1 deel1) (nth 2 deel1) 0 ))
           (setq elm (subst deel2 deel1 elm))
           (print (nth teller elm))
         )         
       )  
     )
     (setq teller (+ teller 1))
  )
  ;(setq elm (subst (list 210 0 0 1) (assoc 210 elm) elm))
  (entmod elm)

)
